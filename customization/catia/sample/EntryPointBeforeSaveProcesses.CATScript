' -----------------------------------------------------------------------------
' Script: PrepProps.CATScript
'
' This scripts scans the active structure and create User defined Props from Parameters
'
' -----------------------------------------------------------------------------
' Version:
' 1.0    08.06.2017    O. Kirsten (LMtec GmbH)           Inital version
' -----------------------------------------------------------------------------
'
' -----------------------------------------------------------------------------
' setting environment
' -----------------------------------------------------------------------------

' public declarations
Public oFileSys As Object            'File System Object
Public oLog As Object                'the log file

Public CATEnv As String              'CATIA Environment Name
Public WORK_DIR As String            'TcIc V5 -> Work Dir -> get from Env Variable
Public TEMP_DIR As String            'User Temp Folder

Public ProArr() As Variant           'array for structure information
Public PropValueArr() As Variant     'array for User Defined Properties
Public PropNameArr() As Variant      'array for Names of User Define Properties Unique

Public iCounter As Integer           'Counter
Public oRowCount As Integer          'Counter
Public lmax As Integer               'maximum level of structure object

' -----------------------------------------------------------------------------
' Here we go ...
' -----------------------------------------------------------------------------

Sub CATMain()

    Dim Start                       'script start time, used to measure running time

    ReDim ProArr(28, 0)
    ReDim PropValueArr(2, 0)
    ReDim PropNameArr(0)
  
    ' ---------------------------------------------------------
    ' 0.) Initialize
    ' ---------------------------------------------------------
    Start = Timer
    oRowCount = 0
   
    Set oLog = Nothing
    
    CATIA.DisplayFileAlerts = False
    
    CATEnv = CATIA.SystemService.Environ("V5ENV")
    WORK_DIR = CATIA.SystemService.Environ("WORK_DIR")
    TEMP_DIR = CATIA.SystemService.Environ("TEMP")
    
    Set oFileSys = CreateObject("Scripting.FileSystemObject")
    
    If oFileSys.FolderExists(WORK_DIR) Then
        Set oLog = oFileSys.CreateTextFile(WORK_DIR & "\tmp\PrepForImport_" & GetTimeStampNoSep() & ".log", True)
    Else
        Set oLog = oFileSys.CreateTextFile(TEMP_DIR & "\PrepForImport_" & GetTimeStampNoSep() & ".log", True)
    End If
    
    LogMsg "CATEnv: " & CATEnv
    
    ' ---------------------------------------------------------
    ' 1.) Check Case - Run specific prepation function
    ' ---------------------------------------------------------
 
    StatusMsg "Start Function ImportCase()"
    ImportCase
    LogMsg "End Function ImportCase()"
    oLog.Close
    
    MsgBox "Prepare Properties finished after " & Round(Timer - Start, 2) & " sec"

End Sub


'----------------------------------------------------------------------------------------------------------------
' ***********************************  Main Step Functions *********************************
'----------------------------------------------------------------------------------------------------------------
' -----------------------------------------------------------------------------
' Sub:  Import Case
'       Check import case
' -----------------------------------------------------------------------------
Function ImportCase()

Dim i  As Integer
Dim ValArr(2) As Variant 'valid values for InputBox
Dim FileArr() As Variant
Dim Text As String
Dim InPro(0)                  'array for insert function
Dim oProDoc As Document


    '### Check any document opened ###
    If CATIA.Windows.Count = 0 Then
        
        '################ Read files in import folder  #################
        
        Set FSO = CreateObject("Scripting.FileSystemObject")
        Set P = FSO.GetFolder(WORK_DIR & "\Import")
        
        i = 0
        For Each F In P.Files
            ReDim Preserve FileArr(i)
            
            ' For multiple CATParts using Dummy Product
            If Right(F.Path, 8) = ".CATPart" Then
                FileArr(i) = F.Path
                i = i + 1
                ValArr(1) = "1"
            End If
            
        Next
        
        If ValArr(1) <> "1" Then
            ErrBox "Opened document unknown for preparation function! - Exit Function"
            Exit Function
        End If
                
        'If ValArr(1) = 1 Then Text = Text & "[1] All CATParts in import folder" & Chr(10)
        'Text = Text & Chr(10) & "Please type number of your selection."
        'Sel = InputBox(Text, "Selection")
        Sel = 1
        
        If Sel = 1 Then
            Set oProDoc = CATIA.Documents.Add("Product")
            
            For Each F In P.Files
                If Right(F.Path, 8) = ".CATPart" Then
                    InPro(0) = F.Path
                    oProDoc.Product.Products.AddComponentsFromFiles InPro, "All"
                End If
            Next
            
        End If
        
        oProDoc.Product.PartNumber = "DUMMY_FOR_IMPORT_" & GetTimeStampNoSep
        oProDoc.SaveAs WORK_DIR & "\import\" & oProDoc.Product.PartNumber & ".CATProduct"
        
        StatusMsg "Start Function WriteProps()for: " & CATIA.ActiveDocument.Name
        AnalyzeStruc CATIA.ActiveDocument.Product, 0, "activated"
        LogMsg "End Function WriteProps()for: " & CATIA.ActiveDocument.Name
        
        '###### Run for all CATDrawings in import folder
        Call ManageDrawings
        
    '### Case CATDrawing
    ElseIf InStr(CATIA.ActiveDocument.Name, ".CATDrawing") <> 0 Then
        
        StatusMsg "Start Function WriteProps() for CATDrawing: " & CATIA.ActiveDocument.Name
        Call WriteProps(CATIA.ActiveDocument)
        LogMsg "End Function WriteProps() for CATDrawing: " & CATIA.ActiveDocument.Name
    
    '### Case CATPart / CATProduct
    ElseIf InStr(CATIA.ActiveDocument.Name, ".CATProduct") <> 0 Or _
           InStr(CATIA.ActiveDocument.Name, ".CATPart") <> 0 Then
        
        StatusMsg "Start Function WriteProps()for: " & CATIA.ActiveDocument.Name
        AnalyzeStruc CATIA.ActiveDocument.Product, 0, "activated"
        LogMsg "End Function WriteProps()for: " & CATIA.ActiveDocument.Name
        
        '###### Run for all CATDrawings in import folder
        Call ManageDrawings
        
    '### Undefined document type
    Else
        ErrBox "Opened document unknown for preparation function! - Exit Function"
        Exit Function
    End If

End Function

' -----------------------------------------------------------------------------
' Sub:  AnalyzeStruc
'       analyzing the structure based on the file opened in CATIA
' Parameters:
'           oCurrentProduct:   Current CATProduct
'           iLevel:            Structure level count
'           sActivStat:        Activation flag
' -----------------------------------------------------------------------------
Sub AnalyzeStruc(oCurrentProduct, iLevel As Integer, sActivStat As String)

    Dim i As Integer               'iterator of child products
    Dim j As Integer
    Dim transf(11)                 'Transformation matrix of the Product
    Dim sActiveStatSub As String
    Dim sublist 'As List
    Dim parameter As parameter
    Dim parameters As parameters
    Dim oChildProducts As Products
    Dim ADoc As Document

    Dim oFileSys As Object
    
    Set parameters = oCurrentProduct.parameters
    
    Set oFileSys = CreateObject("Scripting.FileSystemObject")
    
    oCurrentProduct.Position.GetComponents transf

    '###### activate Default Mode (Design mode) to read properties
    If oCurrentProduct.GetNumberOfShapes <> 0 Then
        oCurrentProduct.ApplyWorkMode DEFAULT_MODE
    End If

    iCounter = iCounter + 1
    oRowCount = oRowCount + 1
    ReDim Preserve ProArr(28, iCounter)

    If iLevel > lmax Then lmax = iLevel    'set lmax to the deepest level

    ProArr(0, iCounter - 1) = oRowCount
    ProArr(1, iCounter - 1) = iLevel
    ProArr(2, iCounter - 1) = oCurrentProduct.Name
    ProArr(3, iCounter - 1) = oCurrentProduct.DescriptionInst
    
    LogMsg "Row: " & oRowCount & " Level:" & iLevel & " Instance Name: " & oCurrentProduct.Name
    
    On Error Resume Next '#####
    
    ProArr(4, iCounter - 1) = oCurrentProduct.ReferenceProduct.Parent.Name
        
    If Err.Number = 0 Then  '#####
        On Error GoTo 0
        StatusMsg "Analyze File: " & oCurrentProduct.ReferenceProduct.Parent.Name
        
        ProArr(5, iCounter - 1) = oFileSys.GetFile(oCurrentProduct.ReferenceProduct.Parent.FullName).Size
        'ProArr(6, iCounter - 1) later in this code -> ParentFilename
        ProArr(7, iCounter - 1) = oCurrentProduct.PartNumber
        ProArr(8, iCounter - 1) = oCurrentProduct.Nomenclature
        ProArr(9, iCounter - 1) = oCurrentProduct.DescriptionRef
        ProArr(10, iCounter - 1) = oCurrentProduct.Definition
        ProArr(11, iCounter - 1) = oCurrentProduct.Revision
        ProArr(12, iCounter - 1) = oCurrentProduct.Source
        
        If oCurrentProduct.GetNumberOfShapes <> 0 Then
            ProArr(13, iCounter - 1) = oCurrentProduct.GetShapePathName(oCurrentProduct.GetDefaultShapeName)
        End If

        If iLevel = 0 Then
            If Right(oCurrentProduct.ReferenceProduct.Parent.Name, 7) = "CATPart" Then
                ProArr(14, iCounter - 1) = "CATPart"
            Else
                ProArr(14, iCounter - 1) = "CATProduct"
            End If
        Else
            If oCurrentProduct.Parent.Parent.ReferenceProduct.Parent.Name = oCurrentProduct.ReferenceProduct.Parent.Name Then
                ProArr(14, iCounter - 1) = "Component"
            ElseIf Right(oCurrentProduct.ReferenceProduct.Parent.Name, 7) = "CATPart" Then
                ProArr(14, iCounter - 1) = "CATPart"
            Else
                ProArr(14, iCounter - 1) = "CATProduct"
            End If
        
            ProArr(6, iCounter - 1) = oCurrentProduct.Parent.Parent.ReferenceProduct.Parent.Name
        
        End If

        ' Write Trafo info to the array
        For j = 0 To 11
            ProArr(j + 16, iCounter - 1) = transf(j)
        Next

        '##############################################################################################
        '############# Prepare Import Properties   ####################################################
        If ProArr(14, iCounter - 1) = "CATPart" Or ProArr(14, iCounter - 1) = "CATProduct" Then
            Call WriteProps(oCurrentProduct.ReferenceProduct)
        End If
        '############# Prepare Import Properties END  #################################################
        '##############################################################################################

        ' Main iteration of this recursive function
        Set oChildProducts = oCurrentProduct.Products
        i = 0
        Do While i < oChildProducts.Count
            i = i + 1
            sActiveStatSub = "activated"
            ProArr(15, iCounter - 1) = sActiveStatSub
            Set sublist = parameters.sublist(oChildProducts.Item(i), False)
            If sublist.Count > 0 Then
                Set parameter = sublist.Item(1)
                If parameter.ValueAsString = "false" Then
                    sActiveStatSub = "deactivated"
                    ProArr(15, iCounter - 1) = sActiveStatSub
                End If
            End If
            AnalyzeStruc oChildProducts.Item(i), iLevel + 1, sActiveStatSub
        Loop
    Else
        ProArr(4, iCounter - 1) = "Missing File"
        ErrMsg "Missing File fir Instance: " & oCurrentProduct.Name
        
    End If

    On Error GoTo 0

End Sub

' -----------------------------------------------------------------------------
' Function: Write UserDefined Properties
' -----------------------------------------------------------------------------
Function WriteProps(oCurrentObject)

Dim i As Integer
Dim j As Integer
Dim oPropArr(1, 3) As Variant   'neu - 3 für Unterscheidung zwischen CATPart, CATProduct, CATDrawing
Dim CatiaFileName As String
Dim oDoc As Document
Dim oPara  As StrParam
Dim OldVal  As String

'### Cases CATDrawing - CATPart / CATProduct
If InStr(oCurrentObject.Name, ".CATDrawing") <> 0 Then
    CatiaFileName = oCurrentObject.Name
Else
    CatiaFileName = oCurrentObject.ReferenceProduct.Parent.Name
End If

CatiaFileNameWE = CatiaFileName

'Remove File extension
CatiaFileName = Left(CatiaFileName, InStrRev(CatiaFileName, ".") - 1)

'############################################################################################
'### Cases extract props from CATIA filename depending on input criteria ####################
'############################################################################################

    oPropArr(0, 0) = "Positionsnummer"
    oPropArr(0, 2) = "TC_Positionsnummer"
    oPropArr(1, 0) = "Produktbezeichnung"
    oPropArr(1, 2) = "TC_Produktbezeichnung"

'############################################################################################
'### Cases End ##############################################################################
'############################################################################################

'### CATPart / CATProduct
If InStr(oCurrentObject.Name, ".CATDrawing") = 0 Then
    LogMsg "Properties Count: " & oCurrentObject.UserRefProperties.Count
    For i = 0 To UBound(oPropArr)
    
        On Error Resume Next
        
        Set oPara = oCurrentObject.parameters.Item(oPropArr(i, 0))
    
        If Err.Number <> 0 Then

        Else
            oPropArr(i, 1) = oPara.Value
            LogMsg "Parameter Update: " & oPara.Name & "=" & oPropArr(i, 1)
          
        End If
        
        On Error GoTo 0
        
        Err.Number = 0
        
        Set oPara = Nothing
                
        On Error Resume Next
                
        Set oPara = oCurrentObject.UserRefProperties.Item(oPropArr(i, 2))
        OldVal = oPara.Value
        oPara.Value = oPropArr(i, 1)
        
        If Err.Number <> 0 Then
            Set oPara = oCurrentObject.UserRefProperties.CreateString(oPropArr(i, 2), "")
            oPara.Value = oPropArr(i, 1)
            LogMsg "Parameter Created: " & oPara.Name & "=" & oPropArr(i, 1)
        Else
            LogMsg "Parameter Exist:  " & oPara.Name & "=" & OldVal
            LogMsg "Parameter Update: " & oPara.Name & "=" & oPropArr(i, 1)
        End If
        
        On Error GoTo 0
        
        Err.Number = 0
        
        Set oPara = Nothing
        
    Next
    
    Set oDoc = oCurrentObject.Parent
    'SaveDoc oDoc
    
'### CATDrawing
Else
    LogMsg "Parameter Count: " & oCurrentObject.parameters.Count
    
    'Overwrite Design ItemType with Drawing Itemtype
    oPropArr(0, 1) = oPropArr(0, 2)
    
    For i = 0 To UBound(oPropArr)
    
        On Error Resume Next
        
        Set oPara = oCurrentObject.parameters.Item(oPropArr(i, 0))
        OldVal = oPara.Value
        oPara.Value = oPropArr(i, 1)
        
        If Err.Number <> 0 Then
            Set oPara = oCurrentObject.parameters.CreateString(oPropArr(i, 0), "")
            oPara.Value = oPropArr(i, 1)
            LogMsg "Parameter Created: " & oPara.Name & "=" & oPropArr(i, 1)
        Else
            LogMsg "Parameter Exist:  " & oPara.Name & "=" & OldVal
            LogMsg "Parameter Update: " & oPara.Name & "=" & oPropArr(i, 1)
        End If
        
        On Error GoTo 0
        
        Err.Number = 0
        
        Set oPara = Nothing
        
    Next
End If

End Function

Function ManageDrawings()

Dim FSO
Dim P
Dim F

Dim oDrwDoc As DrawingDocument
        
Set FSO = CreateObject("Scripting.FileSystemObject")
Set P = FSO.GetFolder(WORK_DIR & "\Import")
        
' Open all drawings in import folder
For Each F In P.Files
    If Right(F.Path, 11) = ".CATDrawing" Then
        Set oDrwDoc = CATIA.Documents.Open(F.Path)
        
        StatusMsg "Start Function WriteProps() for CATDrawing: " & CATIA.ActiveDocument.Name
        Call WriteProps(CATIA.ActiveDocument)
        LogMsg "End Function WriteProps() for CATDrawing: " & CATIA.ActiveDocument.Name
        
        'Call SaveDoc(oDrwDoc)
        oDrwDoc.Close
    End If
Next

End Function

Function SaveDoc(oDoc As Document)

    LogMsg "Start Saving of: " & oDoc.Name
    On Error Resume Next
    'oDoc.Save
    If Err.Number <> 0 Then
        ErrBox "Error during save of document: " & oDoc.Name & " appeared" & Chr(13) & _
               "Error Number: " & Err.Number & Chr(13) & _
               "Please check if Document is Read Only"
        ErrMsg "Error during save of document: " & oDoc.Name & " appeared"
        ErrMsg "Error Number: " & Err.Number
        ErrMsg "Please check if Document is Read Only"
        
    End If
    On Error GoTo 0

End Function

'----------------------------------------------------------------------------------------------------------------
' ************************************  Message & Log Functions ************************************
'----------------------------------------------------------------------------------------------------------------
' -----------------------------------------------------------------------------
' Function: GetTimeStamp
'           Return the time stamp in string form
' -----------------------------------------------------------------------------
Function GetTimeStamp()

    GetTimeStamp = Right("20" & Year(Now()), 4) & "-" & Right("0" & Month(Now()), 2) & "-" & Right("0" & Day(Now()), 2) & _
            " " & Right("0" & Hour(Now()), 2) & ":" & Right("0" & Minute(Now()), 2) & ":" & Right("0" & Second(Now()), 2)
            
End Function

' -----------------------------------------------------------------------------
' Function: GetTimeStampNoSep
'           Return the time stamp in string form without separator
' -----------------------------------------------------------------------------
Function GetTimeStampNoSep()

    GetTimeStampNoSep = Right("20" & Year(Now()), 4) & Right("0" & Month(Now()), 2) & Right("0" & Day(Now()), 2) & _
             Right("0" & Hour(Now()), 2) & Right("0" & Minute(Now()), 2) & Right("0" & Second(Now()), 2)
            
End Function

' -----------------------------------------------------------------------------
' Function: StatusMsg
'           Show the input messages in CATIA status bar and log them, used for main steps
' Parameter:
'       strInput:   String that will be shown in CATIA and write to log file
' -----------------------------------------------------------------------------
Function StatusMsg(strInput)

    CATIA.StatusBar = "Prepare Structure: " & strInput
    LogMsg strInput
    
End Function

' -----------------------------------------------------------------------------
' Function: LogMsg
'           Write input messages to the log file with "LOG:" prefix
' Parameter:
'       strInput:   String that will be write to log file
' -----------------------------------------------------------------------------
Function LogMsg(strInput)
   
    If Not IsEmpty(oLog) And Not (oLog Is Nothing) Then
        oLog.Write GetTimeStamp() & " LOG : " & strInput & Chr(13) & Chr(10)
    End If

End Function

' -----------------------------------------------------------------------------
' Function: ErrBox
'           Open a dialog to show the error message and log them
' Parameter:
'       strInput:   String that will be shown in CATIA and write to log file
' -----------------------------------------------------------------------------
Function ErrBox(strInput)

    StatusMsg "ERROR - " & strInput
    MsgBox strInput, vbCritical, "Prepare Structure - ERROR"
    
End Function

' -----------------------------------------------------------------------------
' Function: ErrMsg
'           Write input messages to the log file with "ERROR:"
' Parameter:
'       strInput:   String that will be write to log file
' -----------------------------------------------------------------------------
Function ErrMsg(strInput)
    
    If Not IsEmpty(oLog) And Not (oLog Is Nothing) Then
        oLog.Write GetTimeStamp() & " ERROR : " & strInput & Chr(13) & Chr(10)
    End If
    
End Function
